module port-aggr {
    namespace "http://nl/surfnet/portaggr";
    prefix "port-aggr";

    import tailf-common {
        prefix tailf;
    }
    import tailf-ncs {
        prefix ncs;
    }
    import junos {
        prefix junos;
    }

    revision 2018-06-01;

    typedef vlan-range {
      type string {
        pattern
          '(409[0-4]|40[0-8][0-9]|[1-3][0-9]{3}|'
            + '[1-9][0-9]{1,2}|[1-9])\.\.(409[0-4]|'
            + '40[0-8][0-9]|[1-3][0-9]{3}|[1-9][0-9]{1,2}|'
            + '[1-9])';
      }
      description
        "Type definition representing a range of single-tagged
      VLANs. A range is specified as x..y where x and y are
      valid VLAN IDs (1 <= vlan-id <= 4094). The range is
      assumed to be inclusive, such that any VLAN-ID matching
      x <= VLAN-ID <= y falls within the range.";
    }

    augment /ncs:services {

        list port-aggr {
            tailf:info "port aggregation service for a device";

            key name;
            unique "device id";

            uses ncs:service-data;
            ncs:servicepoint "port-aggr";

            leaf name {
                tailf:info "port-aggr service name";
                type string {
                    length "5..10" {
                        error-message "name of service should be between 5 and 10 charecters long.";
                    }
                }
            }

            leaf id {
                tailf:info "port-aggr id";
                type uint8 {
                    range "0..15";
                }
                mandatory true;
            }

            leaf vlan-id {
                tailf:info "provide vlan-id range";
                type vlan-range;
            }

            leaf device {
                tailf:info "port-aggr device";
                type leafref {
                    path "/ncs:devices/ncs:device/ncs:name";
                }
                mandatory true;
            }

            leaf-list interfaces {
                description "the individual interfaces of the port-aggr. 
                            We're using re-match and count XPATH must functions to filter correct interfaces without a unit.
                            We also make sure interface is not already being used in other port-aggr service";
                tailf:info "port-aggr interfaces on device";
                type leafref {
                    path "deref(../device)/../ncs:config/junos:configuration/junos:interfaces/junos:interface/junos:name";
                }
                //ncs% show interfaces interface xe-0/0/0 | display prefixes | display xpath
                must "count(deref(../device)/../ncs:config/junos:configuration/junos:interfaces/junos:interface[junos:name=current()]/junos:unit) = 0 " +
                     "and count(../../port-aggr[name != current()/../name]/interfaces = current()) = 0 " +
                     "and re-match(current(),'(ge|xe|te)-.*')" {
                        tailf:dependency "../device";
                        error-message "Please select correct interfaces";
                }                
                min-elements 1;
                max-elements 8;
            }


        }
    }
}
